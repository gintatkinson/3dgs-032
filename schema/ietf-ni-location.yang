module ietf-ni-location {
     yang-version 1.1;
     namespace "urn:ietf:params:xml:ns:yang:ietf-ni-location";
     prefix nil;

     import ietf-yang-types {
       prefix yang;
       reference
         "RFC 6991: Common YANG Data Types";
     }
     import ietf-network-inventory {
       prefix nwi;
       reference
         "RFCAAAA: A YANG Data Model for Network Inventory";
     }
     import ietf-geo-location {
       prefix geo;
       reference
         "RFC 9179: A YANG Grouping for Geographic Locations";
     }

     organization
       "IETF Network Inventory YANG (ivy) Working Group";
     contact
       "WG Web:   <https://datatracker.ietf.org/wg/ivy>
        WG List:  <mailto:inventory-yang@ietf.org>

        Editor: Bo Wu
             <lana.wubo@huawei.com>
        Editor: Sergio Belotti
             <sergio.belotti@nokia.com>
        Editor: Jean-Francois Bouquier
             <jeff.bouquier@vodafone.com>
        Editor: Fabio Peruzzini
             <fabio.peruzzini@telecomitalia.it>
        Editor: Phil Bedard
             <phbedard@cisco.com>";
     description
       "This YANG module defines a model for Network Inventory
        location.

        Copyright (c) 2025 IETF Trust and the persons



Wu, et al.               Expires 8 January 2026                 [Page 9]

Internet-Draft         Network Inventory Location              July 2025


        identified as authors of the code.  All rights reserved.

        Redistribution and use in source and binary forms, with or
        without modification, is permitted pursuant to, and subject
        to the license terms contained in, the Revised BSD License
        set forth in Section 4.c of the IETF Trust's Legal Provisions
        Relating to IETF Documents
        (https://trustee.ietf.org/license-info).

        This version of this YANG module is part of RFC XXXX; see
        the RFC itself for full legal notices.";

     revision 2025-04-17 {
       description
         "Initial version";
       reference
         "RFC XXXX: A YANG Data Model for Network Inventory location.";
       //RFC Editor: Please replace XXXX with actual RFC number,
       //update date information and remove this note
     }

     /* Identities */
     /* Typedef */

     typedef ni-location-ref {
       type leafref {
         path
           "/nwi:network-inventory/nil:locations/nil:location/nil:id";
       }
       description
         "This type is used by data models that need to reference
          network inventory location.";
     }

     /* Grouping */

     grouping physical-address {
       description
         "The grouping of the physical address.";
       container physical-address {
         description
           "Top level container for the physical address.";
         leaf address {
           type string;
           description
             "Specifies an address (number and street).";
         }
         leaf postal-code {



Wu, et al.               Expires 8 January 2026                [Page 10]

Internet-Draft         Network Inventory Location              July 2025


           type string;
           description
             "Specifies a postal code.";
         }
         leaf state {
           type string;
           description
             "Specifies a state. This leaf can also be
              used to describe a region for a country that
              does not have states.";
         }
         leaf city {
           type string;
           description
             "Specifies a city.";
         }
         leaf country-code {
           type string {
             pattern '[A-Z]{2}';
           }
           description
             "Specifies a country.
              Expressed as ISO ALPHA-2 code.";
         }
       }
     }

     grouping locations {
       description
         "The grouping of the locations.";
       container locations {
         description
           "The container for the NE location information.";
         list location {
           key "id";
           description
             "The list of locations within the network.";
           leaf id {
             type string;
             description
               "An identifier of the location.";
           }
           uses nwi:common-entity-attributes;
           leaf type {
             type string;
             description
               "The type of network inventory location, e.g.
                equipment room, building, or site.



Wu, et al.               Expires 8 January 2026                [Page 11]

Internet-Draft         Network Inventory Location              July 2025


                This allows operators to flexibly define custom location
                types (e.g., 'pole', 'roof', 'floor') based on their
                specific network scenarios without requiring model
                extensions. String-based types enable dynamic adaptation
                to heterogeneous organizational naming conventions.";
           }
           leaf parent {
             type leafref {
               path "../../location/id";
             }
             description
               "The name of the location that physically contains this
                location.";
           }
           leaf-list child {
             type leafref {
               path "../../location/id";
             }
             description
               "The name of the contained child locations.";
           }
           leaf timestamp {
             type yang:date-and-time;
             description
               "Reference time when location was recorded.";
           }
           leaf valid-until {
             type yang:date-and-time;
             description
               "The timestamp for which this location is valid until.
                If unspecified, the location has no specific
                expiration time.";
           }
           uses physical-address;
           uses geo:geo-location;
         }
         uses racks;
       }
     }

     grouping racks {
       description
         "The attributes of the rack.";
       container racks {
         description
           "Top level container for the list of racks.";
         list rack {
           key "id";



Wu, et al.               Expires 8 January 2026                [Page 12]

Internet-Draft         Network Inventory Location              July 2025


           description
             "The list of racks within a location,
              e.g. equipment room.";
           leaf id {
             type string;
             description
               "An identifier that uniquely identifies the rack
                within a location, e.g. equipment room.";
           }
           uses nwi:common-entity-attributes;
           container rack-location {
             description
               "The location information of the rack, which
                comprises the name of the location, row number, and
                column number.";
             leaf location-ref {
               type ni-location-ref;
               description
                 "Name of location where this rack is located.";
             }
             leaf row-number {
               type uint32;
               description
                 "Identifies the row within the equipment room where
                  the rack is located.";
             }
             leaf column-number {
               type uint32;
               description
                 "Identifies the physical location of the rack within
                  the column.";
             }
           }
           leaf height {
             type uint16;
             units "millimeter";
             description
               "Rack height.";
           }
           leaf width {
             type uint16;
             units "millimeter";
             description
               "Rack width.";
           }
           leaf depth {
             type uint16;
             units "millimeter";



Wu, et al.               Expires 8 January 2026                [Page 13]

Internet-Draft         Network Inventory Location              July 2025


             description
               "Rack depth.";
           }
           leaf max-voltage {
             type uint16;
             units "volt";
             description
               "The maximum voltage could be supported by the rack.";
           }
           leaf max-allocated-power {
             type uint16;
             units "watts";
             description
               "The maximum allocated power to the rack.";
           }
           list contained-chassis {
             key "relative-position";
             description
               "The list of chassis within a rack.";
             leaf relative-position {
               type uint8;
               description
                 "A relative position of chassis within
                  the rack";
             }
             leaf ne-ref {
               type leafref {
                 path "/nwi:network-inventory/nwi:network-elements"
                    + "/nwi:network-element/nwi:ne-id";
               }
               description
                 "The reference to the network element containing
                  the chassis component.";
             }
             leaf component-ref {
               type leafref {
                 path "/nwi:network-inventory/nwi:network-elements"
                    + "/nwi:network-element[nwi:ne-id=current()/.."
                    + "/ne-ref]/nwi:components/nwi:component"
                    + "/nwi:component-id";
               }
               description
                 "The reference to the chassis component within
                  the network element and contained by the rack.";
             }
           }
           leaf timestamp {
             type yang:date-and-time;



Wu, et al.               Expires 8 January 2026                [Page 14]

Internet-Draft         Network Inventory Location              July 2025


             description
               "Reference time when location was recorded.";
           }
           leaf valid-until {
             type yang:date-and-time;
             description
               "The timestamp for which this location is valid until.
                If unspecified, the location has no specific
                expiration time.";
           }
         }
       }
     }

     grouping locations-ref {
       description
         "The attributes of the locations.";
       container locations {
         description
           "The container for the location.";
         leaf-list location {
           type ni-location-ref;
           description
             "The reference of the location.";
         }
         leaf rack {
           type leafref {
             path "/nwi:network-inventory/nil:locations/nil:racks"
                + "/nil:rack/nil:id";
           }
           description
             "The reference to the rack.";
         }
       }
     }

     augment "/nwi:network-inventory" {
       description
         "Provides location information for network inventory.";
       uses locations;
     }

     augment
       "/nwi:network-inventory/nwi:network-elements"
       + "/nwi:network-element" {
         description
           "Augment network element with location information.";
         uses locations-ref;



Wu, et al.               Expires 8 January 2026                [Page 15]

Internet-Draft         Network Inventory Location              July 2025


     }
   }
